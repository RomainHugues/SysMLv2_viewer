package StressRealization {
    part def OperationalEntity;
    action def SystemFunction;
    part def LogicalComponent;
    part def PhysicalNode;
    part def Op0 :> OperationalEntity;
    part def Op1 :> OperationalEntity;
    part def Op2 :> OperationalEntity;
    part def Op3 :> OperationalEntity;
    part def Op4 :> OperationalEntity;
    part def Op5 :> OperationalEntity;
    part def Op6 :> OperationalEntity;
    part def Op7 :> OperationalEntity;
    part def Op8 :> OperationalEntity;
    part def Op9 :> OperationalEntity;
    part def Op10 :> OperationalEntity;
    part def Op11 :> OperationalEntity;
    action def Sy0 :> SystemFunction;
    action def Sy1 :> SystemFunction;
    action def Sy2 :> SystemFunction;
    action def Sy3 :> SystemFunction;
    action def Sy4 :> SystemFunction;
    action def Sy5 :> SystemFunction;
    action def Sy6 :> SystemFunction;
    action def Sy7 :> SystemFunction;
    action def Sy8 :> SystemFunction;
    action def Sy9 :> SystemFunction;
    action def Sy10 :> SystemFunction;
    action def Sy11 :> SystemFunction;
    part def Lo0 :> LogicalComponent;
    part def Lo1 :> LogicalComponent;
    part def Lo2 :> LogicalComponent;
    part def Lo3 :> LogicalComponent;
    part def Lo4 :> LogicalComponent;
    part def Lo5 :> LogicalComponent;
    part def Lo6 :> LogicalComponent;
    part def Lo7 :> LogicalComponent;
    part def Lo8 :> LogicalComponent;
    part def Lo9 :> LogicalComponent;
    part def Lo10 :> LogicalComponent;
    part def Lo11 :> LogicalComponent;
    part def Ph0 :> PhysicalNode;
    part def Ph1 :> PhysicalNode;
    part def Ph2 :> PhysicalNode;
    part def Ph3 :> PhysicalNode;
    part def Ph4 :> PhysicalNode;
    part def Ph5 :> PhysicalNode;
    part def Ph6 :> PhysicalNode;
    part def Ph7 :> PhysicalNode;
    part def Ph8 :> PhysicalNode;
    part def Ph9 :> PhysicalNode;
    part def Ph10 :> PhysicalNode;
    part def Ph11 :> PhysicalNode;
    dependency from Sy0 to Op0;
    dependency from Sy1 to Op1;
    dependency from Sy2 to Op2;
    dependency from Sy3 to Op3;
    dependency from Sy4 to Op4;
    dependency from Sy5 to Op5;
    dependency from Sy6 to Op6;
    dependency from Sy7 to Op7;
    dependency from Sy8 to Op8;
    dependency from Sy9 to Op9;
    dependency from Sy10 to Op10;
    dependency from Sy11 to Op11;
    dependency from Lo0 to Sy0;
    dependency from Lo1 to Sy1;
    dependency from Lo2 to Sy2;
    dependency from Lo3 to Sy3;
    dependency from Lo4 to Sy4;
    dependency from Lo5 to Sy5;
    dependency from Lo6 to Sy6;
    dependency from Lo7 to Sy7;
    dependency from Lo8 to Sy8;
    dependency from Lo9 to Sy9;
    dependency from Lo10 to Sy10;
    dependency from Lo11 to Sy11;
    dependency from Ph0 to Lo0;
    dependency from Ph1 to Lo1;
    dependency from Ph2 to Lo2;
    dependency from Ph3 to Lo3;
    dependency from Ph4 to Lo4;
    dependency from Ph5 to Lo5;
    dependency from Ph6 to Lo6;
    dependency from Ph7 to Lo7;
    dependency from Ph8 to Lo8;
    dependency from Ph9 to Lo9;
    dependency from Ph10 to Lo10;
    dependency from Ph11 to Lo11;
}
