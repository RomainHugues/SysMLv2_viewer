package StressRequirements {
    part def Sys;
    requirement def Rq0 {
        doc /* Requirement 0. */
    }
    requirement def Rq1 {
        doc /* Requirement 1. */
    }
    requirement def Rq2 {
        doc /* Requirement 2. */
    }
    requirement def Rq3 {
        doc /* Requirement 3. */
    }
    requirement def Rq4 {
        doc /* Requirement 4. */
    }
    requirement def Rq5 {
        doc /* Requirement 5. */
    }
    requirement def Rq6 :> Rq2 {
        doc /* Requirement 6. */
    }
    requirement def Rq7 {
        doc /* Requirement 7. */
    }
    requirement def Rq8 {
        doc /* Requirement 8. */
    }
    requirement def Rq9 :> Rq5 {
        doc /* Requirement 9. */
    }
    requirement def Rq10 {
        doc /* Requirement 10. */
    }
    requirement def Rq11 {
        doc /* Requirement 11. */
    }
    requirement def Rq12 :> Rq8 {
        doc /* Requirement 12. */
    }
    requirement def Rq13 {
        doc /* Requirement 13. */
    }
    requirement def Rq14 {
        doc /* Requirement 14. */
    }
    requirement def Rq15 :> Rq11 {
        doc /* Requirement 15. */
    }
    requirement def Rq16 {
        doc /* Requirement 16. */
    }
    requirement def Rq17 {
        doc /* Requirement 17. */
    }
    requirement def Rq18 :> Rq14 {
        doc /* Requirement 18. */
    }
    requirement def Rq19 {
        doc /* Requirement 19. */
    }
    requirement def Rq20 {
        doc /* Requirement 20. */
    }
    requirement def Rq21 :> Rq17 {
        doc /* Requirement 21. */
    }
    requirement def Rq22 {
        doc /* Requirement 22. */
    }
    requirement def Rq23 {
        doc /* Requirement 23. */
    }
    requirement def Rq24 :> Rq20 {
        doc /* Requirement 24. */
    }
    requirement def Rq25 {
        doc /* Requirement 25. */
    }
    requirement def Rq26 {
        doc /* Requirement 26. */
    }
    requirement def Rq27 :> Rq23 {
        doc /* Requirement 27. */
    }
    requirement def Rq28 {
        doc /* Requirement 28. */
    }
    requirement def Rq29 {
        doc /* Requirement 29. */
    }
    requirement def Rq30 :> Rq26 {
        doc /* Requirement 30. */
    }
    requirement def Rq31 {
        doc /* Requirement 31. */
    }
    requirement def Rq32 {
        doc /* Requirement 32. */
    }
    requirement def Rq33 :> Rq29 {
        doc /* Requirement 33. */
    }
    requirement def Rq34 {
        doc /* Requirement 34. */
    }
    requirement def Rq35 {
        doc /* Requirement 35. */
    }
    requirement def Rq36 :> Rq32 {
        doc /* Requirement 36. */
    }
    requirement def Rq37 {
        doc /* Requirement 37. */
    }
    requirement def Rq38 {
        doc /* Requirement 38. */
    }
    requirement def Rq39 :> Rq35 {
        doc /* Requirement 39. */
    }
    requirement def Rq40 {
        doc /* Requirement 40. */
    }
    requirement def Rq41 {
        doc /* Requirement 41. */
    }
    requirement def Rq42 :> Rq38 {
        doc /* Requirement 42. */
    }
    requirement def Rq43 {
        doc /* Requirement 43. */
    }
    requirement def Rq44 {
        doc /* Requirement 44. */
    }
    requirement def Rq45 :> Rq41 {
        doc /* Requirement 45. */
    }
    requirement def Rq46 {
        doc /* Requirement 46. */
    }
    requirement def Rq47 {
        doc /* Requirement 47. */
    }
    requirement def Rq48 :> Rq44 {
        doc /* Requirement 48. */
    }
    requirement def Rq49 {
        doc /* Requirement 49. */
    }
    requirement def Rq50 {
        doc /* Requirement 50. */
    }
    requirement def Rq51 :> Rq47 {
        doc /* Requirement 51. */
    }
    requirement def Rq52 {
        doc /* Requirement 52. */
    }
    requirement def Rq53 {
        doc /* Requirement 53. */
    }
    requirement def Rq54 :> Rq50 {
        doc /* Requirement 54. */
    }
    requirement def Rq55 {
        doc /* Requirement 55. */
    }
    requirement def Rq56 {
        doc /* Requirement 56. */
    }
    requirement def Rq57 :> Rq53 {
        doc /* Requirement 57. */
    }
    requirement def Rq58 {
        doc /* Requirement 58. */
    }
    requirement def Rq59 {
        doc /* Requirement 59. */
    }
    requirement def Rq60 :> Rq56 {
        doc /* Requirement 60. */
    }
    requirement def Rq61 {
        doc /* Requirement 61. */
    }
    requirement def Rq62 {
        doc /* Requirement 62. */
    }
    requirement def Rq63 :> Rq59 {
        doc /* Requirement 63. */
    }
    requirement def Rq64 {
        doc /* Requirement 64. */
    }
    requirement def Rq65 {
        doc /* Requirement 65. */
    }
    requirement def Rq66 :> Rq62 {
        doc /* Requirement 66. */
    }
    requirement def Rq67 {
        doc /* Requirement 67. */
    }
    requirement def Rq68 {
        doc /* Requirement 68. */
    }
    requirement def Rq69 :> Rq65 {
        doc /* Requirement 69. */
    }
    requirement def Rq70 {
        doc /* Requirement 70. */
    }
    requirement def Rq71 {
        doc /* Requirement 71. */
    }
    requirement def Rq72 :> Rq68 {
        doc /* Requirement 72. */
    }
    requirement def Rq73 {
        doc /* Requirement 73. */
    }
    requirement def Rq74 {
        doc /* Requirement 74. */
    }
    requirement def Rq75 :> Rq71 {
        doc /* Requirement 75. */
    }
    requirement def Rq76 {
        doc /* Requirement 76. */
    }
    requirement def Rq77 {
        doc /* Requirement 77. */
    }
    requirement def Rq78 :> Rq74 {
        doc /* Requirement 78. */
    }
    requirement def Rq79 {
        doc /* Requirement 79. */
    }
    requirement def Spec {
        subject sys : Sys;
        requirement n0 : Rq0;
        requirement n1 : Rq5;
        requirement n2 : Rq10;
        requirement n3 : Rq15;
        requirement n4 : Rq20;
        requirement n5 : Rq25;
        requirement n6 : Rq30;
        requirement n7 : Rq35;
        requirement n8 : Rq40;
        requirement n9 : Rq45;
        requirement n10 : Rq50;
        requirement n11 : Rq55;
        requirement n12 : Rq60;
        requirement n13 : Rq65;
        requirement n14 : Rq70;
        requirement n15 : Rq75;
    }
    dependency from Rq0 to Rq3;
    dependency from Rq9 to Rq12;
    dependency from Rq18 to Rq21;
    dependency from Rq27 to Rq30;
    dependency from Rq36 to Rq39;
    dependency from Rq45 to Rq48;
    dependency from Rq54 to Rq57;
    dependency from Rq63 to Rq66;
    dependency from Rq72 to Rq75;
    part sys : Sys {
        satisfy Rq1;
        satisfy Rq7;
        satisfy Rq13;
        satisfy Rq19;
    }
}
