package StressFlowchart {
    action def BigProcess {
        action a0;
        action a1;
        action a2;
        action a3;
        action a4;
        action a5;
        action a6;
        action a7;
        action a8;
        action a9;
        action a10;
        action a11;
        action a12;
        action a13;
        decide a14;
        action a15;
        action a16;
        action a17;
        action a18;
        action a19;
        action a20;
        action a21;
        action a22;
        action a23;
        action a24;
        action a25;
        action a26;
        action a27;
        action a28;
        decide a29;
        action a30;
        action a31;
        action a32;
        action a33;
        action a34;
        action a35;
        action a36;
        action a37;
        action a38;
        action a39;
        action a40;
        action a41;
        action a42;
        action a43;
        decide a44;
        action a45;
        action a46;
        action a47;
        action a48;
        action a49;
        action a50;
        action a51;
        action a52;
        action a53;
        action a54;
        action a55;
        action a56;
        action a57;
        action a58;
        decide a59;
        action a60;
        action a61;
        action a62;
        action a63;
        action a64;
        action a65;
        action a66;
        action a67;
        action a68;
        action a69;
        action a70;
        action a71;
        action a72;
        action a73;
        decide a74;
        action a75;
        action a76;
        action a77;
        action a78;
        action a79;
        succession first a0 then a1;
        succession first a1 then a2;
        succession first a2 then a3;
        succession first a3 then a4;
        succession first a4 then a5;
        succession first a5 then a6;
        succession first a6 then a7;
        succession first a7 then a8;
        succession first a8 then a9;
        succession first a9 then a10;
        succession first a10 then a11;
        succession first a11 then a12;
        succession first a12 then a13;
        succession first a13 then a14;
        succession first a14 then a15;
        succession first a15 then a16;
        succession first a16 then a17;
        succession first a17 then a18;
        succession first a18 then a19;
        succession first a19 then a20;
        succession first a20 then a21;
        succession first a21 then a22;
        succession first a22 then a23;
        succession first a23 then a24;
        succession first a24 then a25;
        succession first a25 then a26;
        succession first a26 then a27;
        succession first a27 then a28;
        succession first a28 then a29;
        succession first a29 then a30;
        succession first a30 then a31;
        succession first a31 then a32;
        succession first a32 then a33;
        succession first a33 then a34;
        succession first a34 then a35;
        succession first a35 then a36;
        succession first a36 then a37;
        succession first a37 then a38;
        succession first a38 then a39;
        succession first a39 then a40;
        succession first a40 then a41;
        succession first a41 then a42;
        succession first a42 then a43;
        succession first a43 then a44;
        succession first a44 then a45;
        succession first a45 then a46;
        succession first a46 then a47;
        succession first a47 then a48;
        succession first a48 then a49;
        succession first a49 then a50;
        succession first a50 then a51;
        succession first a51 then a52;
        succession first a52 then a53;
        succession first a53 then a54;
        succession first a54 then a55;
        succession first a55 then a56;
        succession first a56 then a57;
        succession first a57 then a58;
        succession first a58 then a59;
        succession first a59 then a60;
        succession first a60 then a61;
        succession first a61 then a62;
        succession first a62 then a63;
        succession first a63 then a64;
        succession first a64 then a65;
        succession first a65 then a66;
        succession first a66 then a67;
        succession first a67 then a68;
        succession first a68 then a69;
        succession first a69 then a70;
        succession first a70 then a71;
        succession first a71 then a72;
        succession first a72 then a73;
        succession first a73 then a74;
        succession first a74 then a75;
        succession first a75 then a76;
        succession first a76 then a77;
        succession first a77 then a78;
        succession first a78 then a79;
    }
}
