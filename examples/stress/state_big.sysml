package StressState {
    state def BigMachine {
        entry; then St0;
        state St0;
        state St1;
        state St2;
        state St3;
        state St4;
        state St5;
        state St6;
        state St7;
        state St8;
        state St9;
        state St10;
        state St11;
        state St12;
        state St13;
        state St14;
        state St15;
        state St16;
        state St17;
        state St18;
        state St19;
        state St20;
        state St21;
        state St22;
        state St23;
        state St24;
        state St25;
        state St26;
        state St27;
        state St28;
        state St29;
        state St30;
        state St31;
        state St32;
        state St33;
        state St34;
        state St35;
        state St36;
        state St37;
        state St38;
        state St39;
        state St40;
        state St41;
        state St42;
        state St43;
        state St44;
        state St45;
        state St46;
        state St47;
        state St48;
        state St49;
        state St50;
        state St51;
        state St52;
        state St53;
        state St54;
        state St55;
        state St56;
        state St57;
        state St58;
        state St59;
        transition first St0 then St1;
        transition first St1 then St2;
        transition first St2 then St3;
        transition first St3 then St4;
        transition first St4 then St5;
        transition first St5 then St6;
        transition first St6 then St7;
        transition first St7 then St8;
        transition first St8 then St9;
        transition first St9 then St10;
        transition first St10 then St11;
        transition first St11 then St12;
        transition first St12 then St13;
        transition first St13 then St14;
        transition first St14 then St15;
        transition first St15 then St16;
        transition first St16 then St17;
        transition first St17 then St18;
        transition first St18 then St19;
        transition first St19 then St20;
        transition first St20 then St21;
        transition first St21 then St22;
        transition first St22 then St23;
        transition first St23 then St24;
        transition first St24 then St25;
        transition first St25 then St26;
        transition first St26 then St27;
        transition first St27 then St28;
        transition first St28 then St29;
        transition first St29 then St30;
        transition first St30 then St31;
        transition first St31 then St32;
        transition first St32 then St33;
        transition first St33 then St34;
        transition first St34 then St35;
        transition first St35 then St36;
        transition first St36 then St37;
        transition first St37 then St38;
        transition first St38 then St39;
        transition first St39 then St40;
        transition first St40 then St41;
        transition first St41 then St42;
        transition first St42 then St43;
        transition first St43 then St44;
        transition first St44 then St45;
        transition first St45 then St46;
        transition first St46 then St47;
        transition first St47 then St48;
        transition first St48 then St49;
        transition first St49 then St50;
        transition first St50 then St51;
        transition first St51 then St52;
        transition first St52 then St53;
        transition first St53 then St54;
        transition first St54 then St55;
        transition first St55 then St56;
        transition first St56 then St57;
        transition first St57 then St58;
        transition first St58 then St59;
        transition first St59 then St0;
        transition first St5 then St25;
        transition first St17 then St37;
        transition first St29 then St49;
        transition first St41 then St1;
        transition first St53 then St13;
    }
}
