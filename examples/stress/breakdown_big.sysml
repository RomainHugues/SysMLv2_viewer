package StressBreakdown {
    action def Fnr {
        action s0 : Fnr0;
        action s1 : Fnr1;
        action s2 : Fnr2;
        action s3 : Fnr3;
        action s4 : Fnr4;
    }
    action def Fnr0 {
        action s0 : Fnr00;
        action s1 : Fnr01;
        action s2 : Fnr02;
        action s3 : Fnr03;
        action s4 : Fnr04;
    }
    action def Fnr1 {
        action s0 : Fnr10;
        action s1 : Fnr11;
        action s2 : Fnr12;
        action s3 : Fnr13;
        action s4 : Fnr14;
    }
    action def Fnr2 {
        action s0 : Fnr20;
        action s1 : Fnr21;
        action s2 : Fnr22;
        action s3 : Fnr23;
        action s4 : Fnr24;
    }
    action def Fnr3 {
        action s0 : Fnr30;
        action s1 : Fnr31;
        action s2 : Fnr32;
        action s3 : Fnr33;
        action s4 : Fnr34;
    }
    action def Fnr4 {
        action s0 : Fnr40;
        action s1 : Fnr41;
        action s2 : Fnr42;
        action s3 : Fnr43;
        action s4 : Fnr44;
    }
    action def Fnr00 {
        action s0 : Fnr000;
        action s1 : Fnr001;
        action s2 : Fnr002;
        action s3 : Fnr003;
        action s4 : Fnr004;
    }
    action def Fnr01 {
        action s0 : Fnr010;
        action s1 : Fnr011;
        action s2 : Fnr012;
        action s3 : Fnr013;
        action s4 : Fnr014;
    }
    action def Fnr02 {
        action s0 : Fnr020;
        action s1 : Fnr021;
        action s2 : Fnr022;
        action s3 : Fnr023;
        action s4 : Fnr024;
    }
    action def Fnr03 {
        action s0 : Fnr030;
        action s1 : Fnr031;
        action s2 : Fnr032;
        action s3 : Fnr033;
        action s4 : Fnr034;
    }
    action def Fnr04 {
        action s0 : Fnr040;
        action s1 : Fnr041;
        action s2 : Fnr042;
        action s3 : Fnr043;
        action s4 : Fnr044;
    }
    action def Fnr10 {
        action s0 : Fnr100;
        action s1 : Fnr101;
        action s2 : Fnr102;
        action s3 : Fnr103;
        action s4 : Fnr104;
    }
    action def Fnr11 {
        action s0 : Fnr110;
        action s1 : Fnr111;
        action s2 : Fnr112;
        action s3 : Fnr113;
        action s4 : Fnr114;
    }
    action def Fnr12 {
        action s0 : Fnr120;
        action s1 : Fnr121;
        action s2 : Fnr122;
        action s3 : Fnr123;
        action s4 : Fnr124;
    }
    action def Fnr13 {
        action s0 : Fnr130;
        action s1 : Fnr131;
        action s2 : Fnr132;
        action s3 : Fnr133;
        action s4 : Fnr134;
    }
    action def Fnr14 {
        action s0 : Fnr140;
        action s1 : Fnr141;
        action s2 : Fnr142;
        action s3 : Fnr143;
        action s4 : Fnr144;
    }
    action def Fnr20 {
        action s0 : Fnr200;
        action s1 : Fnr201;
        action s2 : Fnr202;
        action s3 : Fnr203;
        action s4 : Fnr204;
    }
    action def Fnr21 {
        action s0 : Fnr210;
        action s1 : Fnr211;
        action s2 : Fnr212;
        action s3 : Fnr213;
        action s4 : Fnr214;
    }
    action def Fnr22 {
        action s0 : Fnr220;
        action s1 : Fnr221;
        action s2 : Fnr222;
        action s3 : Fnr223;
        action s4 : Fnr224;
    }
    action def Fnr23 {
        action s0 : Fnr230;
        action s1 : Fnr231;
        action s2 : Fnr232;
        action s3 : Fnr233;
        action s4 : Fnr234;
    }
    action def Fnr24 {
        action s0 : Fnr240;
        action s1 : Fnr241;
        action s2 : Fnr242;
        action s3 : Fnr243;
        action s4 : Fnr244;
    }
    action def Fnr30 {
        action s0 : Fnr300;
        action s1 : Fnr301;
        action s2 : Fnr302;
        action s3 : Fnr303;
        action s4 : Fnr304;
    }
    action def Fnr31 {
        action s0 : Fnr310;
        action s1 : Fnr311;
        action s2 : Fnr312;
        action s3 : Fnr313;
        action s4 : Fnr314;
    }
    action def Fnr32 {
        action s0 : Fnr320;
        action s1 : Fnr321;
        action s2 : Fnr322;
        action s3 : Fnr323;
        action s4 : Fnr324;
    }
    action def Fnr33 {
        action s0 : Fnr330;
        action s1 : Fnr331;
        action s2 : Fnr332;
        action s3 : Fnr333;
        action s4 : Fnr334;
    }
    action def Fnr34 {
        action s0 : Fnr340;
        action s1 : Fnr341;
        action s2 : Fnr342;
        action s3 : Fnr343;
        action s4 : Fnr344;
    }
    action def Fnr40 {
        action s0 : Fnr400;
        action s1 : Fnr401;
        action s2 : Fnr402;
        action s3 : Fnr403;
        action s4 : Fnr404;
    }
    action def Fnr41 {
        action s0 : Fnr410;
        action s1 : Fnr411;
        action s2 : Fnr412;
        action s3 : Fnr413;
        action s4 : Fnr414;
    }
    action def Fnr42 {
        action s0 : Fnr420;
        action s1 : Fnr421;
        action s2 : Fnr422;
        action s3 : Fnr423;
        action s4 : Fnr424;
    }
    action def Fnr43 {
        action s0 : Fnr430;
        action s1 : Fnr431;
        action s2 : Fnr432;
        action s3 : Fnr433;
        action s4 : Fnr434;
    }
    action def Fnr44 {
        action s0 : Fnr440;
        action s1 : Fnr441;
        action s2 : Fnr442;
        action s3 : Fnr443;
        action s4 : Fnr444;
    }
    action def Fnr000;
    action def Fnr001;
    action def Fnr002;
    action def Fnr003;
    action def Fnr004;
    action def Fnr010;
    action def Fnr011;
    action def Fnr012;
    action def Fnr013;
    action def Fnr014;
    action def Fnr020;
    action def Fnr021;
    action def Fnr022;
    action def Fnr023;
    action def Fnr024;
    action def Fnr030;
    action def Fnr031;
    action def Fnr032;
    action def Fnr033;
    action def Fnr034;
    action def Fnr040;
    action def Fnr041;
    action def Fnr042;
    action def Fnr043;
    action def Fnr044;
    action def Fnr100;
    action def Fnr101;
    action def Fnr102;
    action def Fnr103;
    action def Fnr104;
    action def Fnr110;
    action def Fnr111;
    action def Fnr112;
    action def Fnr113;
    action def Fnr114;
    action def Fnr120;
    action def Fnr121;
    action def Fnr122;
    action def Fnr123;
    action def Fnr124;
    action def Fnr130;
    action def Fnr131;
    action def Fnr132;
    action def Fnr133;
    action def Fnr134;
    action def Fnr140;
    action def Fnr141;
    action def Fnr142;
    action def Fnr143;
    action def Fnr144;
    action def Fnr200;
    action def Fnr201;
    action def Fnr202;
    action def Fnr203;
    action def Fnr204;
    action def Fnr210;
    action def Fnr211;
    action def Fnr212;
    action def Fnr213;
    action def Fnr214;
    action def Fnr220;
    action def Fnr221;
    action def Fnr222;
    action def Fnr223;
    action def Fnr224;
    action def Fnr230;
    action def Fnr231;
    action def Fnr232;
    action def Fnr233;
    action def Fnr234;
    action def Fnr240;
    action def Fnr241;
    action def Fnr242;
    action def Fnr243;
    action def Fnr244;
    action def Fnr300;
    action def Fnr301;
    action def Fnr302;
    action def Fnr303;
    action def Fnr304;
    action def Fnr310;
    action def Fnr311;
    action def Fnr312;
    action def Fnr313;
    action def Fnr314;
    action def Fnr320;
    action def Fnr321;
    action def Fnr322;
    action def Fnr323;
    action def Fnr324;
    action def Fnr330;
    action def Fnr331;
    action def Fnr332;
    action def Fnr333;
    action def Fnr334;
    action def Fnr340;
    action def Fnr341;
    action def Fnr342;
    action def Fnr343;
    action def Fnr344;
    action def Fnr400;
    action def Fnr401;
    action def Fnr402;
    action def Fnr403;
    action def Fnr404;
    action def Fnr410;
    action def Fnr411;
    action def Fnr412;
    action def Fnr413;
    action def Fnr414;
    action def Fnr420;
    action def Fnr421;
    action def Fnr422;
    action def Fnr423;
    action def Fnr424;
    action def Fnr430;
    action def Fnr431;
    action def Fnr432;
    action def Fnr433;
    action def Fnr434;
    action def Fnr440;
    action def Fnr441;
    action def Fnr442;
    action def Fnr443;
    action def Fnr444;
}
