package StressClass {
    part def Base0;
    part def Base1;
    part def Base2;
    part def C0 :> Base0 {
        part p0a : C1;
        part p0b : C7;
    }
    part def C1 :> Base1 {
        part p1a : C2;
        part p1b : C8;
    }
    part def C2 :> Base2 {
        part p2a : C3;
        part p2b : C9;
    }
    part def C3 :> Base0 {
        part p3a : C4;
        part p3b : C10;
    }
    part def C4 :> Base1 {
        part p4a : C5;
        part p4b : C11;
    }
    part def C5 :> Base2 {
        part p5a : C6;
        part p5b : C12;
    }
    part def C6 :> Base0 {
        part p6a : C7;
        part p6b : C13;
    }
    part def C7 :> Base1 {
        part p7a : C8;
        part p7b : C14;
    }
    part def C8 :> Base2 {
        part p8a : C9;
        part p8b : C15;
    }
    part def C9 :> Base0 {
        part p9a : C10;
        part p9b : C16;
    }
    part def C10 :> Base1 {
        part p10a : C11;
        part p10b : C17;
    }
    part def C11 :> Base2 {
        part p11a : C12;
        part p11b : C18;
    }
    part def C12 :> Base0 {
        part p12a : C13;
        part p12b : C19;
    }
    part def C13 :> Base1 {
        part p13a : C14;
        part p13b : C20;
    }
    part def C14 :> Base2 {
        part p14a : C15;
        part p14b : C21;
    }
    part def C15 :> Base0 {
        part p15a : C16;
        part p15b : C22;
    }
    part def C16 :> Base1 {
        part p16a : C17;
        part p16b : C23;
    }
    part def C17 :> Base2 {
        part p17a : C18;
        part p17b : C24;
    }
    part def C18 :> Base0 {
        part p18a : C19;
        part p18b : C25;
    }
    part def C19 :> Base1 {
        part p19a : C20;
        part p19b : C26;
    }
    part def C20 :> Base2 {
        part p20a : C21;
        part p20b : C27;
    }
    part def C21 :> Base0 {
        part p21a : C22;
        part p21b : C28;
    }
    part def C22 :> Base1 {
        part p22a : C23;
        part p22b : C29;
    }
    part def C23 :> Base2 {
        part p23a : C24;
        part p23b : C30;
    }
    part def C24 :> Base0 {
        part p24a : C25;
        part p24b : C31;
    }
    part def C25 :> Base1 {
        part p25a : C26;
        part p25b : C32;
    }
    part def C26 :> Base2 {
        part p26a : C27;
        part p26b : C33;
    }
    part def C27 :> Base0 {
        part p27a : C28;
        part p27b : C34;
    }
    part def C28 :> Base1 {
        part p28a : C29;
        part p28b : C35;
    }
    part def C29 :> Base2 {
        part p29a : C30;
        part p29b : C36;
    }
    part def C30 :> Base0 {
        part p30a : C31;
        part p30b : C37;
    }
    part def C31 :> Base1 {
        part p31a : C32;
        part p31b : C38;
    }
    part def C32 :> Base2 {
        part p32a : C33;
        part p32b : C39;
    }
    part def C33 :> Base0 {
        part p33a : C34;
        part p33b : C40;
    }
    part def C34 :> Base1 {
        part p34a : C35;
        part p34b : C41;
    }
    part def C35 :> Base2 {
        part p35a : C36;
        part p35b : C42;
    }
    part def C36 :> Base0 {
        part p36a : C37;
        part p36b : C43;
    }
    part def C37 :> Base1 {
        part p37a : C38;
        part p37b : C44;
    }
    part def C38 :> Base2 {
        part p38a : C39;
        part p38b : C45;
    }
    part def C39 :> Base0 {
        part p39a : C40;
        part p39b : C46;
    }
    part def C40 :> Base1 {
        part p40a : C41;
        part p40b : C47;
    }
    part def C41 :> Base2 {
        part p41a : C42;
        part p41b : C48;
    }
    part def C42 :> Base0 {
        part p42a : C43;
        part p42b : C49;
    }
    part def C43 :> Base1 {
        part p43a : C44;
        part p43b : C50;
    }
    part def C44 :> Base2 {
        part p44a : C45;
        part p44b : C51;
    }
    part def C45 :> Base0 {
        part p45a : C46;
        part p45b : C52;
    }
    part def C46 :> Base1 {
        part p46a : C47;
        part p46b : C53;
    }
    part def C47 :> Base2 {
        part p47a : C48;
        part p47b : C54;
    }
    part def C48 :> Base0 {
        part p48a : C49;
        part p48b : C55;
    }
    part def C49 :> Base1 {
        part p49a : C50;
        part p49b : C56;
    }
    part def C50 :> Base2 {
        part p50a : C51;
        part p50b : C57;
    }
    part def C51 :> Base0 {
        part p51a : C52;
        part p51b : C58;
    }
    part def C52 :> Base1 {
        part p52a : C53;
        part p52b : C59;
    }
    part def C53 :> Base2 {
        part p53a : C54;
        part p53b : C60;
    }
    part def C54 :> Base0 {
        part p54a : C55;
        part p54b : C61;
    }
    part def C55 :> Base1 {
        part p55a : C56;
        part p55b : C62;
    }
    part def C56 :> Base2 {
        part p56a : C57;
        part p56b : C63;
    }
    part def C57 :> Base0 {
        part p57a : C58;
        part p57b : C64;
    }
    part def C58 :> Base1 {
        part p58a : C59;
        part p58b : C65;
    }
    part def C59 :> Base2 {
        part p59a : C60;
        part p59b : C66;
    }
    part def C60 :> Base0 {
        part p60a : C61;
        part p60b : C67;
    }
    part def C61 :> Base1 {
        part p61a : C62;
        part p61b : C68;
    }
    part def C62 :> Base2 {
        part p62a : C63;
        part p62b : C69;
    }
    part def C63 :> Base0 {
        part p63a : C64;
        part p63b : C70;
    }
    part def C64 :> Base1 {
        part p64a : C65;
        part p64b : C71;
    }
    part def C65 :> Base2 {
        part p65a : C66;
        part p65b : C72;
    }
    part def C66 :> Base0 {
        part p66a : C67;
        part p66b : C73;
    }
    part def C67 :> Base1 {
        part p67a : C68;
        part p67b : C74;
    }
    part def C68 :> Base2 {
        part p68a : C69;
        part p68b : C75;
    }
    part def C69 :> Base0 {
        part p69a : C70;
        part p69b : C76;
    }
    part def C70 :> Base1 {
        part p70a : C71;
        part p70b : C77;
    }
    part def C71 :> Base2 {
        part p71a : C72;
        part p71b : C78;
    }
    part def C72 :> Base0 {
        part p72a : C73;
        part p72b : C79;
    }
    part def C73 :> Base1 {
        part p73a : C74;
        part p73b : C80;
    }
    part def C74 :> Base2 {
        part p74a : C75;
        part p74b : C81;
    }
    part def C75 :> Base0 {
        part p75a : C76;
        part p75b : C82;
    }
    part def C76 :> Base1 {
        part p76a : C77;
        part p76b : C83;
    }
    part def C77 :> Base2 {
        part p77a : C78;
        part p77b : C84;
    }
    part def C78 :> Base0 {
        part p78a : C79;
        part p78b : C85;
    }
    part def C79 :> Base1 {
        part p79a : C80;
        part p79b : C86;
    }
    part def C80 :> Base2 {
        part p80a : C81;
        part p80b : C87;
    }
    part def C81 :> Base0 {
        part p81a : C82;
        part p81b : C88;
    }
    part def C82 :> Base1 {
        part p82a : C83;
        part p82b : C89;
    }
    part def C83 :> Base2 {
        part p83a : C84;
        part p83b : C90;
    }
    part def C84 :> Base0 {
        part p84a : C85;
        part p84b : C91;
    }
    part def C85 :> Base1 {
        part p85a : C86;
        part p85b : C92;
    }
    part def C86 :> Base2 {
        part p86a : C87;
        part p86b : C93;
    }
    part def C87 :> Base0 {
        part p87a : C88;
        part p87b : C94;
    }
    part def C88 :> Base1 {
        part p88a : C89;
        part p88b : C95;
    }
    part def C89 :> Base2 {
        part p89a : C90;
        part p89b : C96;
    }
    part def C90 :> Base0 {
        part p90a : C91;
        part p90b : C97;
    }
    part def C91 :> Base1 {
        part p91a : C92;
        part p91b : C98;
    }
    part def C92 :> Base2 {
        part p92a : C93;
        part p92b : C99;
    }
    part def C93 :> Base0 {
        part p93a : C94;
        part p93b : C100;
    }
    part def C94 :> Base1 {
        part p94a : C95;
        part p94b : C101;
    }
    part def C95 :> Base2 {
        part p95a : C96;
        part p95b : C102;
    }
    part def C96 :> Base0 {
        part p96a : C97;
        part p96b : C103;
    }
    part def C97 :> Base1 {
        part p97a : C98;
        part p97b : C104;
    }
    part def C98 :> Base2 {
        part p98a : C99;
        part p98b : C105;
    }
    part def C99 :> Base0 {
        part p99a : C100;
        part p99b : C106;
    }
    part def C100 :> Base1 {
        part p100a : C101;
        part p100b : C107;
    }
    part def C101 :> Base2 {
        part p101a : C102;
        part p101b : C108;
    }
    part def C102 :> Base0 {
        part p102a : C103;
        part p102b : C109;
    }
    part def C103 :> Base1 {
        part p103a : C104;
        part p103b : C110;
    }
    part def C104 :> Base2 {
        part p104a : C105;
        part p104b : C111;
    }
    part def C105 :> Base0 {
        part p105a : C106;
        part p105b : C112;
    }
    part def C106 :> Base1 {
        part p106a : C107;
        part p106b : C113;
    }
    part def C107 :> Base2 {
        part p107a : C108;
        part p107b : C114;
    }
    part def C108 :> Base0 {
        part p108a : C109;
        part p108b : C115;
    }
    part def C109 :> Base1 {
        part p109a : C110;
        part p109b : C116;
    }
    part def C110 :> Base2 {
        part p110a : C111;
        part p110b : C117;
    }
    part def C111 :> Base0 {
        part p111a : C112;
        part p111b : C118;
    }
    part def C112 :> Base1 {
        part p112a : C113;
        part p112b : C119;
    }
    part def C113 :> Base2 {
        part p113a : C114;
    }
    part def C114 :> Base0 {
        part p114a : C115;
    }
    part def C115 :> Base1 {
        part p115a : C116;
    }
    part def C116 :> Base2 {
        part p116a : C117;
    }
    part def C117 :> Base0 {
        part p117a : C118;
    }
    part def C118 :> Base1 {
        part p118a : C119;
    }
    part def C119 :> Base2 {
    }
}
