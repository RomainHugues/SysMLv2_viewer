package StressSequence {
    part def P0;
    part def P1;
    part def P2;
    part def P3;
    part def P4;
    part def P5;
    part def P6;
    part def P7;
    part def P8;
    part def P9;
    part def P10;
    part def P11;
    part def P12;
    part def P13;
    part def P14;
    part def P15;
    part p0 : P0;
    part p1 : P1;
    part p2 : P2;
    part p3 : P3;
    part p4 : P4;
    part p5 : P5;
    part p6 : P6;
    part p7 : P7;
    part p8 : P8;
    part p9 : P9;
    part p10 : P10;
    part p11 : P11;
    part p12 : P12;
    part p13 : P13;
    part p14 : P14;
    part p15 : P15;
    flow m0 from p0 to p1;
    flow m1 from p1 to p2;
    flow m2 from p2 to p3;
    flow m3 from p3 to p4;
    flow m4 from p4 to p5;
    flow m5 from p5 to p6;
    flow m6 from p6 to p7;
    flow m7 from p7 to p8;
    flow m8 from p8 to p9;
    flow m9 from p9 to p10;
    flow m10 from p10 to p11;
    flow m11 from p11 to p12;
    flow m12 from p12 to p13;
    flow m13 from p13 to p14;
    flow m14 from p14 to p15;
    flow m15 from p15 to p0;
    flow m16 from p0 to p1;
    flow m17 from p1 to p2;
    flow m18 from p2 to p3;
    flow m19 from p3 to p4;
    flow m20 from p4 to p5;
    flow m21 from p5 to p6;
    flow m22 from p6 to p7;
    flow m23 from p7 to p8;
    flow m24 from p8 to p9;
    flow m25 from p9 to p10;
    flow m26 from p10 to p11;
    flow m27 from p11 to p12;
    flow m28 from p12 to p13;
    flow m29 from p13 to p14;
    flow m30 from p14 to p15;
    flow m31 from p15 to p0;
    flow m32 from p0 to p1;
    flow m33 from p1 to p2;
    flow m34 from p2 to p3;
    flow m35 from p3 to p4;
    flow m36 from p4 to p5;
    flow m37 from p5 to p6;
    flow m38 from p6 to p7;
    flow m39 from p7 to p8;
    flow m40 from p8 to p9;
    flow m41 from p9 to p10;
    flow m42 from p10 to p11;
    flow m43 from p11 to p12;
    flow m44 from p12 to p13;
    flow m45 from p13 to p14;
    flow m46 from p14 to p15;
    flow m47 from p15 to p0;
    flow m48 from p0 to p1;
    flow m49 from p1 to p2;
    flow m50 from p2 to p3;
    flow m51 from p3 to p4;
    flow m52 from p4 to p5;
    flow m53 from p5 to p6;
    flow m54 from p6 to p7;
    flow m55 from p7 to p8;
    flow m56 from p8 to p9;
    flow m57 from p9 to p10;
    flow m58 from p10 to p11;
    flow m59 from p11 to p12;
    flow m60 from p12 to p13;
    flow m61 from p13 to p14;
    flow m62 from p14 to p15;
    flow m63 from p15 to p0;
    flow m64 from p0 to p1;
    flow m65 from p1 to p2;
    flow m66 from p2 to p3;
    flow m67 from p3 to p4;
    flow m68 from p4 to p5;
    flow m69 from p5 to p6;
    flow m70 from p6 to p7;
    flow m71 from p7 to p8;
    flow m72 from p8 to p9;
    flow m73 from p9 to p10;
    flow m74 from p10 to p11;
    flow m75 from p11 to p12;
    flow m76 from p12 to p13;
    flow m77 from p13 to p14;
    flow m78 from p14 to p15;
    flow m79 from p15 to p0;
}
